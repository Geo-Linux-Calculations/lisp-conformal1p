(defun gc:GetVector (p1 p2)
  (mapcar '- p2 p1)
)

(defun gc:CrossProduct (v1 v2)
  (setq
    dx1  (car v1)
	dy1  (cadr v1)
	dz1  (caddr v1)
    dx2  (car v2)
	dy2  (cadr v2)
	dz2  (caddr v2)
	gx   (- (* dy1 dz2) (* dz1 dy2))
	gy   (- (* dz1 dx2) (* dx1 dz2))
	gz   (- (* dx1 dy2) (* dy1 dx2))
  )
  (list	gx gy gz)
)

(defun gc:CrossNorm (g)
  (setq
	g0  (list 0.0 0.0 0.0)
	l   (distance g0 g)
    ls  (list l l l)
  )
  (mapcar '/ g ls)
)

(defun gc:MidPoint (p1 p2)
  (mapcar (function (lambda (x1 x2) (* (+ x1 x2) 0.5))) p1 p2)
)

(defun gc:func3Dcircle3P (p1 p2 p3 / v1 v2 norm m1 m2 cen)
  (setq
    v1   (gc:GetVector p1 p2)
	v2   (gc:GetVector p2 p3)
	plac (gc:CrossProduct v1 v2)
	norm (gc:CrossNorm plac)
	m1   (gc:Midpoint p1 p2)
	m2   (gc:Midpoint p2 p3)
	g1   (gc:CrossProduct v1 norm)
	g2   (gc:CrossProduct v2 norm)
	t1   (mapcar '- m1 g1)
	t2   (mapcar '- m2 g2)
	cen  (inters m1 t1 m2 t2 nil)
	cc   (trans cen 0 norm)
	crad (distance cen p1)
  )
 (princ "\n v1: ")
 (princ v1)
 (princ "\n v2: ")
 (princ v2)
 (princ "\n place: ")
 (princ plac)
 (princ "\n norm: ")
 (princ norm)
 (princ "\n m1: ")
 (princ m1)
 (princ "\n m2: ")
 (princ m2)
 (princ "\n g1: ")
 (princ g1)
 (princ "\n g2: ")
 (princ g2)
 (princ "\n t1: ")
 (princ t1)
 (princ "\n t2: ")
 (princ t2)
 (princ "\n cen: ")
 (princ cen)
 (princ "\n cc: ")
 (princ cc)
 (princ "\n crad: ")
 (princ crad)

  (entmakex
    (list
      (cons 0 "CIRCLE")
      (cons 10 cc)
      (cons 40 crad)
      (cons 210 norm)
    )
  )
)

(defun c:3Dcircle3P (/ p1 p2 p3)
 (setq p1 (getpoint "\n Circle point #1: "))
 (princ p1)
 (setq p2 (getpoint "\n Circle point #2: "))
 (princ p2)
 (setq p3 (getpoint "\n Circle point #3: "))
 (princ p3)

 (gc:func3Dcircle3P p1 p2 p3)
 (princ)
)
